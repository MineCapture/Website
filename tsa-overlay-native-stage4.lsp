;;; TSA Stage 4.0 native AutoLISP CAD overlay extraction - validation build.
;;; Run TSAOVL4TEST with the correct section UCS active (after XSTART).
;;; Does not modify drawing or upload to Supabase.
;;; Supported: LINE, LWPOLYLINE, POLYLINE, CIRCLE, ARC, TEXT, MTEXT,
;;; ATTRIB, INSERT (nested static blocks), MULTILEADER, HATCH (solid circular loops).
;;; Unsupported hatch geometry is reported; no invented fill or geometry.
(vl-load-com)
(setq tsa4:layers '("Planning" "XoversXsect" "XoversOffSection"))
(defun tsa4:g (code data) (cdr (assoc code data)))
(defun tsa4:num (n) (if (numberp n) (rtos (float n) 2 12) "0"))
(defun tsa4:bool (x) (if x "true" "false"))
(defun tsa4:esc (s / i c out k)
  (setq i 1 out "" s (if s (vl-princ-to-string s) ""))
  (while (<= i (strlen s))
    (setq c (substr s i 1) k (ascii c))
    (setq out (strcat out (cond ((= k 34) "\\\"") ((= k 92) "\\\\")
      ((= k 10) "\\n") ((= k 13) "\\r") ((= k 9) "\\t")
      ((< k 32) " ") (T c))))
    (setq i (1+ i))) out)
(defun tsa4:q (s) (strcat "\"" (tsa4:esc s) "\""))
(defun tsa4:join (lst sep / out)
  (setq out "") (foreach a lst (setq out (strcat out (if (= out "") "" sep) a))) out)
(defun tsa4:pair (k v) (strcat (tsa4:q k) ":" v))
(defun tsa4:obj (pairs) (strcat "{" (tsa4:join pairs ",") "}"))
(defun tsa4:arr (items) (strcat "[" (tsa4:join items ",") "]"))
(defun tsa4:point (p) (tsa4:arr (list (tsa4:num (car p)) (tsa4:num (cadr p)))))
(defun tsa4:vec3 (p) (list (car p) (cadr p) (if (caddr p) (caddr p) 0.0)))
(defun tsa4:v+ (a b) (mapcar '+ a b))
(defun tsa4:v- (a b) (mapcar '- a b))
(defun tsa4:v* (a s) (mapcar '(lambda (n) (* n s)) a))
(defun tsa4:ident () (list '(0.0 0.0 0.0) '(1.0 0.0 0.0) '(0.0 1.0 0.0) '(0.0 0.0 1.0)))
(defun tsa4:apply (m p / q)
  (setq q (tsa4:vec3 p))
  (tsa4:v+ (car m) (tsa4:v+ (tsa4:v* (cadr m) (car q))
     (tsa4:v+ (tsa4:v* (caddr m) (cadr q)) (tsa4:v* (cadddr m) (caddr q))))))
(defun tsa4:world (en p mat / local)
  ;; Convert entity OCS to its owner's coordinate system, then apply block placement.
  (setq local (if en (trans (tsa4:vec3 p) en 0) (tsa4:vec3 p)))
  (tsa4:apply mat local))
(defun tsa4:xy (p) (tsa4:point (trans p 0 1)))
(defun tsa4:xypt (en p mat) (tsa4:xy (tsa4:world en p mat)))
(defun tsa4:dist-section (p q) (distance (trans p 0 1) (trans q 0 1)))
(defun tsa4:hex (c / h)
  (setq c (fix (max 0 (min 255 c))) h "0123456789ABCDEF")
  (strcat (substr h (1+ (fix (/ c 16))) 1) (substr h (1+ (rem c 16)) 1)))
(defun tsa4:rgb (n) (strcat "#" (tsa4:hex (lsh n -16)) (tsa4:hex (logand (lsh n -8) 255)) (tsa4:hex (logand n 255))))
(defun tsa4:color (en d / tc aci obj col v)
  (cond ((tsa4:g 420 d) (tsa4:rgb (tsa4:g 420 d)))
    ((and (tsa4:g 62 d) (<= 1 (abs (tsa4:g 62 d))) (<= (abs (tsa4:g 62 d)) 255))
     (setq aci (abs (tsa4:g 62 d)))
     ;; Resolve ACI without opening any UI dialog.
     (tsa4:aci aci))
    (T (progn
      (setq obj (vl-catch-all-apply 'vlax-ename->vla-object (list en)))
      (if (not (vl-catch-all-error-p obj))
        (progn (setq v (vl-catch-all-apply 'vla-get-TrueColor (list obj)))
          (if (not (vl-catch-all-error-p v))
            (progn (setq col (vl-catch-all-apply 'vla-get-RGB (list v)))
              (if (and col (numberp col)) (tsa4:rgb col) (tsa4:aci 7)))
            (tsa4:aci 7))) (tsa4:aci 7))))))
(defun tsa4:aci (idx / aciObj rgb)
  (setq aciObj (vl-catch-all-apply 'vla-GetInterfaceObject
    (list (vlax-get-acad-object) "AutoCAD.AcCmColor.24")))
  (if (vl-catch-all-error-p aciObj) (setq aciObj nil))
  (if aciObj
    (progn (vl-catch-all-apply 'vla-put-ColorIndex (list aciObj idx))
      (setq rgb (vl-catch-all-apply 'vla-get-RGB (list aciObj)))
      (if (vl-catch-all-error-p rgb) "#FFFFFF" (tsa4:rgb rgb)))
    (cond ((= idx 1) "#FF0000") ((= idx 2) "#FFFF00") ((= idx 3) "#00FF00")
      ((= idx 4) "#00FFFF") ((= idx 5) "#0000FF") ((= idx 6) "#FF00FF")
      ((= idx 7) "#FFFFFF") (T "#FFFFFF"))))
(defun tsa4:warn (lyr h typ reason)
  (setq tsa4:warnings (cons (tsa4:obj (list (tsa4:pair "layer" (tsa4:q lyr))
    (tsa4:pair "handle" (tsa4:q h)) (tsa4:pair "entityType" (tsa4:q typ))
    (tsa4:pair "message" (tsa4:q reason)))) tsa4:warnings))
  (setq tsa4:nwarn (1+ tsa4:nwarn)))
(defun tsa4:base (d layer parent / h typ aci col)
  (setq h (tsa4:g 5 d) typ (tsa4:g 0 d) col (tsa4:color (handent h) d))
  (append (list (tsa4:pair "handle" (tsa4:q h)) (tsa4:pair "layer" (tsa4:q layer))
     (tsa4:pair "originalLayer" (tsa4:q (if (tsa4:g 8 d) (tsa4:g 8 d) layer)))
     (tsa4:pair "colour" (tsa4:q (if (and (member (strcase layer) '("XOVERSXSECT" "XOVERSOFFSECTION")) (= typ "CIRCLE")) "#000000" col)))
     (tsa4:pair "linetype" (tsa4:q (if (tsa4:g 6 d) (tsa4:g 6 d) "ByLayer")))
     (tsa4:pair "lineweight" (tsa4:num (if (tsa4:g 370 d) (tsa4:g 370 d) -1))))
    (if parent (list (tsa4:pair "parentBlockHandle" (tsa4:q parent))) nil)))
(defun tsa4:add (layer pieces) (if pieces (progn (setq tsa4:entities (cons (tsa4:obj pieces) tsa4:entities)) (setq tsa4:count (1+ tsa4:count)))))
(defun tsa4:ptlist (pts) (tsa4:arr (mapcar 'tsa4:xy pts)))
(defun tsa4:curvpts (en mat / obj maxp i p points err)
  (setq obj (vlax-ename->vla-object en) maxp (vl-catch-all-apply 'vlax-curve-getEndParam (list en)) i 0 points nil)
  (if (vl-catch-all-error-p maxp) nil
    (progn (while (<= i maxp)
      (setq p (vl-catch-all-apply 'vlax-curve-getPointAtParam (list en (float i))))
      (if (not (vl-catch-all-error-p p)) (setq points (cons (tsa4:apply mat p) points)))
      (setq i (1+ i))) (reverse points))))
(defun tsa4:samplecurve (en mat / e n i p pts)
  (setq e (vl-catch-all-apply 'vlax-curve-getEndParam (list en)))
  (if (vl-catch-all-error-p e) nil
    (progn (setq n (max 12 (min 144 (* 12 (max 1 (fix e)))))) i 0 pts nil)
      (repeat (1+ n)
        (setq p (vl-catch-all-apply 'vlax-curve-getPointAtParam (list en (* e (/ (float i) n)))))
        (if (not (vl-catch-all-error-p p)) (setq pts (cons (tsa4:apply mat p) pts)))
        (setq i (1+ i))) (reverse pts)))
(defun tsa4:matrix-block (d parent / norm pos sx sy sz a ax ay az base origin c s)
  (setq norm (if (tsa4:g 210 d) (tsa4:g 210 d) '(0.0 0.0 1.0))
    pos (trans (tsa4:vec3 (tsa4:g 10 d)) norm 0)
    sx (if (tsa4:g 41 d) (tsa4:g 41 d) 1.0)
    sy (if (tsa4:g 42 d) (tsa4:g 42 d) 1.0)
    sz (if (tsa4:g 43 d) (tsa4:g 43 d) 1.0)
    a (if (tsa4:g 50 d) (tsa4:g 50 d) 0.0)
    c (cos a) s (sin a))
  (setq ax (trans (list (* sx c) (* sx s) 0.0) norm 0 T)
        ay (trans (list (* (- sy s)) (* sy c) 0.0) norm 0 T)
        az (trans (list 0.0 0.0 sz) norm 0 T))
  (setq base (tblsearch "BLOCK" (tsa4:g 2 d)))
  (setq origin (if (and base (tsa4:g 10 base)) (tsa4:g 10 base) '(0.0 0.0 0.0)))
  (list (tsa4:v- (tsa4:apply parent pos)
           (tsa4:v+ (tsa4:v* (tsa4:applydir parent ax) (car origin))
             (tsa4:v+ (tsa4:v* (tsa4:applydir parent ay) (cadr origin))
               (tsa4:v* (tsa4:applydir parent az) (caddr origin)))))
    (tsa4:applydir parent ax) (tsa4:applydir parent ay) (tsa4:applydir parent az)))
(defun tsa4:applydir (m p)
  (tsa4:v+ (tsa4:v* (cadr m) (car p)) (tsa4:v+ (tsa4:v* (caddr m) (cadr p)) (tsa4:v* (cadddr m) (caddr p)))))
(defun tsa4:block (en d layer mat depth parent / name rec child cm att tag val b d2)
  (setq name (tsa4:g 2 d))
  (cond ((>= depth 8) (tsa4:warn layer (tsa4:g 5 d) "INSERT" "Nested block depth exceeded"))
    ((not (tblsearch "BLOCK" name)) (tsa4:warn layer (tsa4:g 5 d) "INSERT" "Missing block definition"))
    (T
      (setq rec (tblsearch "BLOCK" name))
      (if (/= 0 (logand 12 (if (tsa4:g 70 rec) (tsa4:g 70 rec) 0)))
        (tsa4:warn layer (tsa4:g 5 d) "INSERT" "External reference omitted")
        (progn
          (setq cm (tsa4:matrix-block d mat))
          (setq child (entnext (tblobjname "BLOCK" name)))
          (while (and child (/= (tsa4:g 0 (entget child)) "ENDBLK"))
            (setq d2 (entget child))
            (if (/= (tsa4:g 0 d2) "ATTDEF")
              (tsa4:extract child layer cm (1+ depth) (tsa4:g 5 d)))
            (setq child (entnext child)))
          ;; Live block attributes, not ATTDEF defaults.
          (setq att (entnext en))
          (while (and att (= (tsa4:g 0 (entget att)) "ATTRIB"))
            (tsa4:extract att layer mat (1+ depth) (tsa4:g 5 d))
            (setq att (entnext att))))))))
(defun tsa4:mleader (en d layer mat parent / context leader ln val code txt arrow landing text name row pts)
  (setq context nil leader nil ln nil txt nil arrow nil landing nil)
  (foreach item d
    (setq code (car item) val (cdr item))
    (cond ((and (= code 300) (= val "CONTEXT_DATA{")) (setq context T leader nil ln nil))
      ((and context (= code 302) (= val "LEADER{")) (setq leader T ln nil))
      ((and context leader (= code 304) (= val "LEADER_LINE{")) (setq ln T))
      ((and context leader ln (= code 305) (= val "}")) (setq ln nil))
      ((and context leader (not ln) (= code 303) (= val "}")) (setq leader nil))
      ((and context (not leader) (= code 301) (= val "}")) (setq context nil))
      ((and context (not leader) (= code 12) (listp val) (null txt)) (setq txt val))
      ((and context (not leader) (= code 110) (listp val) (null arrow)) (setq arrow val))
      ((and context leader (not ln) (= code 10) (listp val) (null landing)) (setq landing val))))
  (setq text (tsa4:g 304 d))
  (if (or (null text) (= text ""))
    (progn (setq row (vl-catch-all-apply 'vla-get-TextString (list (vlax-ename->vla-object en))))
      (if (not (vl-catch-all-error-p row)) (setq text row))))
  (if (and txt text (not (= text "")))
    (progn
      (setq row (append (tsa4:base d layer parent) (list (tsa4:pair "type" (tsa4:q "MLEADER"))
          (tsa4:pair "text" (tsa4:q text)) (tsa4:pair "position" (tsa4:xypt nil txt mat))
          (tsa4:pair "height" (tsa4:num (if (tsa4:g 41 d) (tsa4:g 41 d) 0.3))))))
      (if (and arrow landing)
        (setq row (append row (list (tsa4:pair "points" (tsa4:arr
          (list (tsa4:xypt nil arrow mat) (tsa4:xypt nil landing mat))))))))
      (tsa4:add layer row))
    (tsa4:warn layer (tsa4:g 5 d) "MULTILEADER" "No reliable MLeader text anchor/content")))
(defun tsa4:hatch (en d layer mat parent / pattern solid boundaries entity mode edges loop edge cnt kind arc cen rad a0 a1 owner i current col key)
  (setq solid (= (strcase (if (tsa4:g 2 d) (tsa4:g 2 d) "")) "SOLID"))
  (if (not solid)
    (tsa4:warn layer (tsa4:g 5 d) "HATCH" "Pattern hatch not exported")
    (progn
      ;; Hatch DXF code 92 starts each loop. Codes 72, 10, 40, 50, 51
      ;; describe circular arc edges. 97/330 may reference an associative source.
      (setq mode nil kind nil cen nil rad nil a0 nil a1 nil owner nil)
      (foreach item d
        (setq key (car item))
        (cond ((= key 92) (setq mode T kind nil cen nil rad nil a0 nil a1 nil owner nil))
          ((and mode (= key 72)) (setq kind (cdr item)))
          ((and mode (= key 10) (= kind 2)) (setq cen (cdr item)))
          ((and mode (= key 40) (= kind 2)) (setq rad (cdr item)))
          ((and mode (= key 50) (= kind 2)) (setq a0 (cdr item)))
          ((and mode (= key 51) (= kind 2)) (setq a1 (cdr item)))
          ((and mode (= key 330)) (setq owner (cdr item)))))
      (cond
        ((and owner (entget owner) (= (tsa4:g 0 (entget owner)) "CIRCLE"))
         (setq tsa4:fills (cons (cons (tsa4:g 5 (entget owner)) (tsa4:color en d)) tsa4:fills)))
        ((and cen rad a0 a1
           (< (abs (- (abs (- a1 a0)) (* 2 pi))) 0.01))
         ;; Use actual stored circular hatch loop, not bounding box matching.
         (setq tsa4:filled (cons (list (tsa4:world en (append cen (list 0.0)) mat)
           rad (tsa4:color en d)) tsa4:filled)))
        (T (tsa4:warn layer (tsa4:g 5 d) "HATCH" "Solid hatch boundary not a supported full circle; not guessed"))))))
(defun tsa4:extract (en layer mat depth parent / d typ row p pts cen rad height rot txt)
  (setq d (entget en) typ (tsa4:g 0 d))
  (cond
    ((= typ "INSERT") (tsa4:block en d layer mat depth parent))
    ((= typ "HATCH") (tsa4:hatch en d layer mat parent))
    ((= typ "MULTILEADER") (tsa4:mleader en d layer mat parent))
    (T
      (setq row (tsa4:base d layer parent))
      (cond
        ((= typ "LINE")
          (setq row (append row (list (tsa4:pair "type" (tsa4:q "LINE"))
            (tsa4:pair "points" (tsa4:arr (list (tsa4:xypt en (tsa4:g 10 d) mat)
              (tsa4:xypt en (tsa4:g 11 d) mat))))))))
        ((member typ '("LWPOLYLINE" "POLYLINE"))
          (setq pts (tsa4:samplecurve en mat))
          (if (and pts (> (length pts) 1))
            (setq row (append row (list (tsa4:pair "type" (tsa4:q "POLYLINE"))
              (tsa4:pair "points" (tsa4:ptlist pts))
              (tsa4:pair "closed" (tsa4:bool (/= 0 (logand 1 (if (tsa4:g 70 d) (tsa4:g 70 d) 0))))))))
            (setq row nil)))
        ((= typ "CIRCLE")
          (setq cen (tsa4:world en (tsa4:g 10 d) mat) rad (tsa4:g 40 d))
          (setq row (append row (list (tsa4:pair "type" (tsa4:q "CIRCLE"))
            (tsa4:pair "centre" (tsa4:xy cen)) (tsa4:pair "radius" (tsa4:num rad)))))
          (setq tsa4:circles (cons (list (tsa4:g 5 d) cen rad) tsa4:circles))
          (setq tsa4:circleRows (cons (list (tsa4:g 5 d) row) tsa4:circleRows))
          (setq row nil))
        ((= typ "ARC")
          (setq pts (tsa4:samplecurve en mat))
          (if pts
            (setq row (append row (list (tsa4:pair "type" (tsa4:q "POLYLINE"))
              (tsa4:pair "points" (tsa4:ptlist pts)) (tsa4:pair "closed" "false"))))
            (setq row nil)))
        ((member typ '("TEXT" "ATTRIB" "MTEXT"))
          (setq txt (if (tsa4:g 1 d) (tsa4:g 1 d) ""))
          (if (= typ "MTEXT")
            (progn (setq txt "")
              (foreach a d (if (member (car a) '(1 3)) (setq txt (strcat txt (cdr a)))))))
          (setq p (if (tsa4:g 10 d) (tsa4:g 10 d) '(0.0 0.0 0.0))
            height (if (tsa4:g 40 d) (tsa4:g 40 d) 0.3)
            rot (if (tsa4:g 50 d) (tsa4:g 50 d) 0.0))
          (setq row (append row (list (tsa4:pair "type" (tsa4:q (if (= typ "MTEXT") "MTEXT" "TEXT")))
            (tsa4:pair "text" (tsa4:q txt)) (tsa4:pair "position" (tsa4:xypt en p mat))
            (tsa4:pair "height" (tsa4:num height)) (tsa4:pair "rotation" (tsa4:num rot)))))
          (if (= typ "ATTRIB")
            (setq row (append row (list (tsa4:pair "attributeTag" (tsa4:q (if (tsa4:g 2 d) (tsa4:g 2 d) "")))))))
          (if (= typ "MTEXT")
            (setq row (append row (list (tsa4:pair "width" (tsa4:num (if (tsa4:g 41 d) (tsa4:g 41 d) 0.0))))))))
        (T (setq row nil) (tsa4:warn layer (tsa4:g 5 d) typ "Unsupported entity type")))
      (tsa4:add layer row))))
(defun tsa4:fillcircles (lyr / c f match centre rad fill row p v)
  (foreach c (reverse tsa4:circleRows)
    (setq row (cadr c) match (assoc (car c) tsa4:fills))
    (if (null match)
      (progn (setq centre (cadr (assoc (car c) tsa4:circles))
                   rad (caddr (assoc (car c) tsa4:circles)))
        (foreach f tsa4:filled
          (if (and (< (distance centre (car f)) 0.025) (< (abs (- rad (cadr f))) 0.025))
            (setq match (cons (car c) (caddr f)))))))
    (if match (setq row (append row (list (tsa4:pair "fill" (tsa4:q (cdr match))))))
      (tsa4:warn lyr (car c) "CIRCLE" "No verified solid hatch fill"))
    (tsa4:add lyr row)))
(defun tsa4:timestamp ()
  (menucmd "M=$(edtime,$(getvar,date),YYYY-MM-DDTHH:MM:SS)"))
(defun tsa4:run (rid path / layers results layer ss i en d f content start found total summary)
  (setq tsa4:warnings nil tsa4:nwarn 0 results nil total 0)
  (foreach layer tsa4:layers
    (setq tsa4:entities nil tsa4:count 0 tsa4:circles nil tsa4:circleRows nil tsa4:fills nil tsa4:filled nil)
    (setq ss (ssget "_X" (list (cons 8 layer) (cons 410 "Model"))))
    (if (not (tblsearch "LAYER" layer))
      (tsa4:warn layer "" "LAYER" "Required drawing layer is missing"))
    (if ss (progn (setq i 0)
      (while (< i (sslength ss))
        (setq en (ssname ss i) d (entget en))
        (setq tsa4:lastError (vl-catch-all-apply 'tsa4:extract (list en layer (tsa4:ident) 0 nil)))
        (if (vl-catch-all-error-p tsa4:lastError)
          (tsa4:warn layer (if (tsa4:g 5 d) (tsa4:g 5 d) "") (if (tsa4:g 0 d) (tsa4:g 0 d) "UNKNOWN")
            (strcat "Extractor error: " (vl-catch-all-error-message tsa4:lastError))))
        (setq i (1+ i)))))
    (tsa4:fillcircles layer)
    (setq total (+ total tsa4:count))
    (prompt (strcat "\n" layer ": " (itoa tsa4:count) " output primitives"))
    (setq results (append results (list (tsa4:obj
      (list (tsa4:pair "layerName" (tsa4:q layer))
            (tsa4:pair "layerExists" (tsa4:bool (if (tblsearch "LAYER" layer) T nil)))
            (tsa4:pair "entities" (tsa4:arr (reverse tsa4:entities)))))))))
  (setq content (tsa4:obj (list (tsa4:pair "formatVersion" "1")
     (tsa4:pair "source" (tsa4:q "CAD_OVERLAY"))
     (tsa4:pair "sourceDrawing" (tsa4:q (getvar "DWGNAME")))
     (tsa4:pair "sourceRevision" (tsa4:q (tsa4:timestamp)))
     (tsa4:pair "section" (tsa4:obj (list (tsa4:pair "RdID" (itoa rid))
        (tsa4:pair "coordinateSystem" (tsa4:q "CHAINAGE_ELEVATION"))
        (tsa4:pair "units" (tsa4:q "metres")))))
     (tsa4:pair "layers" (tsa4:arr results))
     (tsa4:pair "warnings" (tsa4:arr (reverse tsa4:warnings)))
     (tsa4:pair "summary" (tsa4:obj (list (tsa4:pair "warningCount" (itoa tsa4:nwarn))
        (tsa4:pair "layerCount" "3")))))))
  (setq f (open path "w"))
  (if f (progn (write-line content f) (close f)
      (prompt (strcat "\nStage 4 TEST JSON: " path " | " (itoa total) " primitives, " (itoa tsa4:nwarn) " warnings.")))
    (prompt "\nERROR: Could not write output JSON."))
  (princ))
(defun c:TSAOVL4TEST (/ rid path)
  (setq rid (if (and (boundp 'secrid) (numberp secrid)) (fix secrid) nil))
  (if (null rid) (setq rid (getint "\nRoadway RdID (from XSTART): ")))
  (if (or (null rid) (<= rid 0)) (prompt "\nInvalid RdID; nothing exported.")
    (progn (setq path (getfiled "Stage 4 TEST export - do not upload until verified"
      "C:\\Temp\\TSA_section_overlay_stage4_TEST.json" "json" 1))
      (if path (tsa4:run rid path))))
  (princ))
(princ "\nTSA Stage 4 native extractor loaded. Run TSAOVL4TEST (read-only, local export).")
(princ)
